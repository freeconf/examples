module car {

    revision 0;
    
    typedef state {
        type enumeration {
            enum outOfGas;
            enum running;
        }
    }

    leaf state {
        type state;
    }

    leaf speed {
       type int32;
       default 100;
    }               

    leaf miles {
       type int64;
       config false;
    }

    leaf gas {
        type int32;
        config false;        
    }     

    notification update {
        leaf state {
            type state;
        }
    }

    rpc refuel {
        input {
            leaf gas {
                type int32;
            }
        }
    }
}
